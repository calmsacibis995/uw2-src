Network-Management-MIB DEFINITIONS ::= BEGIN

            --
            -- This MIB document is 'WORK IN PROGRESS' of Novell, Inc.
            -- As such, it is subject to change, without notice, until
            -- such time as it is formally released and moved from the
            -- novell.experimental tree to the novell.mibDoc tree.
            --
            --
            -- Last Updated: September 16, 1993
            --

            EXPORTS
               NWTime;

            IMPORTS
               enterprises
                  FROM RFC1155-SMI

               OBJECT-TYPE
                  FROM RFC-1212;

            novell         OBJECT IDENTIFIER ::= { enterprises 23 }

            mibDoc         OBJECT IDENTIFIER ::= { novell 2 }
            nExperimental  OBJECT IDENTIFIER ::= { novell 4 }

            nwUnixWare     OBJECT IDENTIFIER ::= { nExperimental 2 }
               END
